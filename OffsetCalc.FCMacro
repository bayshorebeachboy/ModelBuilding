from PySide import QtGui, QtCore

class OffsetCalc(QtGui.QDialog):
	""""""
	def __init__(self):
		super(OffsetCalc, self).__init__()
		self.initUI()
	def initUI(self):
		self.result = userCancelled

		# setting font and size
		# create our window
		# define window		xLoc,yLoc,xDim,yDim
		self.setGeometry(	850, 550, 250, 250)
		self.setWindowTitle("Ship Offset Calculator")
		self.setWindowFlags(QtCore.Qt.WindowStaysOnTopHint)
		# creating a label widget
        		# by default label will display at top left corner
 
		# The beginning of the coordinate system is at the left top corner. 
		# The x values grow from left to right. The y values grow from top to bottom.
		self.label1 = QtGui.QLabel("Station", self)
		self.label1.setFont('Courier') # set to a non-proportional font
		self.label1.move(20, 20)

		self.label2 = QtGui.QLabel("WL/HT!", self)
		self.label2.setFont('Courier') # set to a non-proportional font
		self.label2.move(20, 50)

		self.label3 = QtGui.QLabel("Feet", self)
		self.label3.setFont('Courier') # set to a non-proportional font
		self.label3.move(20, 80)

		self.label4 = QtGui.QLabel("Inches", self)
		self.label4.setFont('Courier') # set to a non-proportional font
		self.label4.move(20, 110)
		
		self.label5 = QtGui.QLabel("Eights", self)
		self.label5.setFont('Courier') # set to a non-proportional font
		self.label5.move(20,140)


		# numeric input field
		self.numericInput = QtGui.QLineEdit(self)
		self.numericInput.setInputMask("999")
		#self.numericInput.setText("000")
		self.numericInput.setFixedWidth(50)
		self.numericInput.move(100, 20)

		self.numericInput1 = QtGui.QLineEdit(self)
		self.numericInput1.setInputMask("999")
		#self.numericInput1.setText("000 ")
		self.numericInput1.setFixedWidth(50)
		self.numericInput1.move(100, 50)

		self.numericInput2= QtGui.QLineEdit(self)
		self.numericInput2.setInputMask("999")
		#self.numericInput2.setText("000")
		self.numericInput2.setFixedWidth(50)
		self.numericInput2.move(100, 80)

		self.numericInput3 = QtGui.QLineEdit(self)
		self.numericInput3.setInputMask("999")
		#self.numericInput3.setText("000 ")
		self.numericInput3.setFixedWidth(50)
		self.numericInput3.move(100, 110)

		self.numericInput4 = QtGui.QLineEdit(self)
		self.numericInput4.setInputMask("999")
		#self.numericInput4.setText("000 ")
		self.numericInput4.setFixedWidth(50)
		self.numericInput4.move(100, 140)




		self.show()

	def onCancel(self):
		self.result			= userCancelled
		self.close()
	def onOk(self):
		self.result			= userOK
		self.close()
	def mousePressEvent(self, event):
		# print mouse position, X & Y
		print("X = ", event.pos().x())
		print("Y = ", event.pos().y())
		#
userCancelled = "Cancelled"
userOK = "OK"

form = OffsetCalc()
form.exec_()
